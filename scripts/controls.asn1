CONTROLS DEFINITIONS ::=

BEGIN

  -- For reference [MS-ADTS]: 3.1.1.3.4.1.6 LDAP_SERVER_GET_STATS_OID
  -- Unused in Samba
  StatsResponseValueV3 ::= SEQUENCE
  {
      threadCountTag        INTEGER,
      threadCount           INTEGER,
      callTimeTag           INTEGER,
      callTime              INTEGER,
      entriesReturnedTag    INTEGER,
      entriesReturned       INTEGER,
      entriesVisitedTag     INTEGER,
      entriesVisited        INTEGER,
      filterTag             INTEGER,
      filter                OCTET STRING,
      indexTag              INTEGER,
      index                 OCTET STRING,
      pagesReferencedTag    INTEGER,
      pagesReferenced       INTEGER,
      pagesReadTag          INTEGER,
      pagesRead             INTEGER,
      pagesPrereadTag       INTEGER,
      pagesPreread          INTEGER,
      pagesDirtiedTag       INTEGER,
      pagesDirtied          INTEGER,
      pagesRedirtiedTag     INTEGER,
      pagesRedirtied        INTEGER,
      logRecordCountTag     INTEGER,
      logRecordCount        INTEGER,
      logRecordBytesTag     INTEGER,
      logRecordBytes        INTEGER
  }

  -- https://www.rfc-editor.org/rfc/rfc2251.txt
  maxInt INTEGER ::= 2147483647 -- (2^^31 - 1) --

  -- [MS-ADTS] 3.1.1.3.4.1.11 LDAP_SERVER_SD_FLAGS_OID
  SDFlagsRequestValue ::= SEQUENCE
  {
      flags                 INTEGER
  }

  -- https://www.rfc-editor.org/rfc/rfc2696.txt
  PagedResultsControlValue ::= SEQUENCE
  {
      size                  INTEGER (0..maxInt),
                             -- requested page size from client
                             -- result set size estimate from server
      cookie                OCTET STRING
  }

END
